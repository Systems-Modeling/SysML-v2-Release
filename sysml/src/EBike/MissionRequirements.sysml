package MissionRequirements{
	doc 'Requirements' /* This package contains the requirements of the mission */
	private import EnterpriseRequirementsDefinitionLibrary::*;
	// Only the requirements are needed for the specification of the system. The requirement definitions are needed only to define the requirements, therefore we import them private // 
}
