package MissionAnalysis{
	doc 'Mission Analysis' /* Analysis at the mision level is meant to describe how efficient the system is */
	import RiskMetadata::*;
	//the mission configuration shall be imported here
	// for each analysis a package shall be made
}
