package EBikeVerification{
	doc 'EBike Verification' /* The Verification cases at the SoI level are described here */
	// the SoI configuration shall be imported here
	// the following library contains VeredictKind
	import VerificationCases::*;
	package VerificationCasesDefinitions{
		doc 'Verification Cases Definition' /* The definition elements of the verification cases are defined here */
	}
	package VerificationsCasesUsage{
		doc 'Verification Cases Usage' /* The Verification cases for the EBike are defined here */
	}
	package VerificationEBike{
		doc 'Verification EBike' /* The sequence of verification cases to fully verify the EBike are defined here */
	}
}
