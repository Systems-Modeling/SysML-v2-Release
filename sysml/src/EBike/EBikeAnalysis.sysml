package EBikeAnalysis{
	doc 'EBike Analysis' /* Analysis at the SoI level is meant to describe what measures of performance characterise the system */
	import RiskMetadata::*;
	//the EBike configuration shall be imported here
	// for each analysis a package shall be made
}
