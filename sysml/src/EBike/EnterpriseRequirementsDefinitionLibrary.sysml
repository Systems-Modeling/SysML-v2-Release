library package EnterpriseRequirementsDefinitionLibrary{
	doc 'Enterprise Requirements Definition' /* This library contains the requirement definitions for all kinds of EBike */
	package MissionRequirementsDefinition{
		doc 'Mission Requirements Definition' /* This package contains the operational requirement definitions for all kinds of Missions */
	}
	package SystemRequirementsDefinition{
		doc 'System Requirements Definition' /* This package contains the system requirement definitions for all kinds of EBike */
	}
}
