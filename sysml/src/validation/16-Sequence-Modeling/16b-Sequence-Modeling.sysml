package '16b-Sequence-Modeling' {
	import ScalarValues::*;
	import PayloadDefinitions::*;

	package PayloadDefinitions {
	    item def Subscribe {
	    	attribute topic : String;
	    	ref part subscriber;
	    }
	    
		item def Publish {
			attribute topic : String;
			ref publication;
		}
		
		item def Deliver {
			ref publication;
		}
	}

	occurrence def PubSubSequence {
		part producer[1] {
			event publish_message::source;
		}
		
		message publish_message of Publish[1];
		
		part server[1] {
			event subscribe_message::target;
			then event publish_message::target;
			then event deliver_message::source;
		}
		
		message subscribe_message of Subscribe[1];
		message deliver_message of Deliver[1];
		
		part consumer[1] {
			event subscribe_message::source;
			then event subscribe_message::target;
		}
	}
}
