package 'Filtering Example-1' {
	import ScalarValues::Boolean;
	
	attribute def Safety {
		attribute isMandatory : Boolean;
	}
	
	part vehicle {
		part interior {
			part alarm;
			part seatBelt[2] {@Safety{isMandatory = true;}}
			part frontSeat[2];
			part driverAirBag {@Safety{isMandatory = false;}}
		}
		part bodyAssy {
			part body;
			part bumper {@Safety{isMandatory = true;}}
			part keylessEntry;
		}
		part wheelAssy {
			part wheel[2];
			part antilockBrakes[2] {@Safety{isMandatory = false;}}
		}
	}
	
	package 'Safety Features' {
		/* Parts that contribute to safety. */		
		import vehicle::**[@Safety];
	}
	
	part 'Safety Assembly' {
		/* Parts that contribute to safety AND are mandatory. */
		import vehicle::**[@Safety && Safety::isMandatory];
	}
}
